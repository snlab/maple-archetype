module maple-l-type {
    namespace "urn:opendaylight:params:xml:ns:yang:maple:l:type";
	prefix "mlt";

	import maple-tracetree {prefix mt;}
	organization "Maple";
	description "augment maple tracetree to support leaf type";

    augment "/mt:tracetrees/mt:maple-apps/mt:ttnodes"{
        when "type == 'L'";
	    list link {
			key "link-id";
			leaf link-id {
				type string;
			}
			container src-node {
				leaf node-id {
					type string;
				}
				leaf port {
					type string;
				}
			}
            container dst-node {
				leaf node-id {
					type string;
				}
				leaf port {
					type string;
				}
			}
		}
    }
}
