module mapleapp-impl {
    yang-version 1;
    namespace "urn:opendaylight:params:xml:ns:yang:mapleapp:impl";
    prefix "mapleapp-impl";

    import config { prefix config; revision-date 2013-04-05; }
    import opendaylight-md-sal-binding { prefix md-sal-binding; revision-date 2013-10-28;}

    description
        "Service definition for mapleapp project";

    revision "2014-12-10" {
        description
            "Initial revision";
    }

    identity mapleapp {
        base config:module-type;
        config:java-name-prefix Mapleapp;
    }

    augment "/config:modules/config:module/config:configuration" {
        case mapleapp {
            when "/config:modules/config:module/config:type = 'mapleapp'";

            leaf chain {
                type string;
            }

            container broker {
                uses config:service-ref {
                    refine type {
                        mandatory true;
                        config:required-identity md-sal-binding:binding-broker-osgi-registry;
                    }
                }
            }
        }
    }
}
