module host-store {
    yang-version 1;
    namespace "urn:maple:increment";
    prefix "host-store";

    revision "2016-09-20" {
        description "Initial revision of host table store";
    }
    container host-table {
        list host-item {
            leaf host-id {
                type int32;
            }
            key host-id;
            leaf tp-id {
                type string;
            }
        }
    }
}
