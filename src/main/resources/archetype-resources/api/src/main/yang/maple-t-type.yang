module maple-t-type {
    namespace "urn:opendaylight:params:xml:ns:yang:maple:t:type";
	prefix "mtt";

	import maple-tracetree {prefix mt;}
	organization "Maple";
	description "augment maple tracetree to support t type";

   revision 2015-11-14 {
		description "initial version of tracetree t node";
	}
    augment "/mt:tracetree/mt:ttnode"{
        when "type == 'T'";
	    leaf field {
			type string;
		}
    }
}
